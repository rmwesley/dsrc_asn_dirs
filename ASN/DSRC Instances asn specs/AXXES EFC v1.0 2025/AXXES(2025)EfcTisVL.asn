EfcTisVlCipCardme {axxes(1) tis(1) vl(0) version0(0) minorVersion1(1)}
DEFINITIONS AUTOMATIC TAGS 
::= BEGIN
EXPORTS ALL;
IMPORTS
-- ********* ISO 17573-3:2022 *********
	TimeCompact, Month
	FROM EfcDataDictionary {iso(1) standard(0) 17573 dd(3) version1(1) minorVersion1(1)} WITH SUCCESSORS;

CodePays ::= INTEGER(0..1023)
NumeroDeOrdreSociete ::= INTEGER(0..99)
CodeSociete ::= SEQUENCE{
	code-pays CodePays,
	numero-sca NumeroDeOrdreSociete
}
NumeroClient ::= INTEGER(1..9999999)
NumeroPorteur ::= INTEGER(1..99999)

F-IDU ::= SEQUENCE{
	code-societe-emettrice CodeSociete,
	numero-client NumeroClient,
	numero-porteur NumeroPorteur
}

NumeroDeOrdreProduit ::= OCTET STRING(SIZE(2))
NumeroListeGare ::= INTEGER(1..9999)
NumeroListeCalendrier ::= INTEGER(1..99)
Date-YYMM-Tis ::= SEQUENCE{
	year INTEGER(0..99),
	month INTEGER(0..12)
}

D-PRO ::= SEQUENCE{
	numero-produit NumeroDeOrdreProduit,
	numero-liste-gare NumeroListeGare,
	numero-liste-calendrier NumeroListeCalendrier,
	date-fin-validite Date-YYMM-Tis
}

DernierPointDePassage ::= INTEGER(0..15)
NumeroDeOrdre ::= INTEGER(0..999)
CodeGare ::= SEQUENCE{
	code-societe-circulee CodeSociete,
	numero-d-ordre NumeroDeOrdre
}
NumeroDeVoie ::= INTEGER(0..99)
SensDeLaVoie ::= BOOLEAN
ClasseVehicule ::= INTEGER(0..15)
Date-YMMDD-Tis ::= SEQUENCE{
	year INTEGER(0..9),
	month Month,
	day INTEGER(0..31) -- day 0 only allowed as no date (year 0, month 0, day 0)
}
HeureDuPassage ::= TimeCompact
PeriodeDeTarif ::= INTEGER(0..9)
TypeDeTarif ::= INTEGER(0..9)
CoutDeLaTransactionTTC ::= INTEGER(0..999999)
CaractereDeObservation ::= INTEGER(0..127)
PointeurDeHistorique ::= INTEGER(0..15)

D-VET ::= SEQUENCE{
	dernier-point-de-passage DernierPointDePassage,
	code-gare CodeGare,
	numero-de-voie NumeroDeVoie,
	sens-de-la-voie SensDeLaVoie,
	classe-vehicule ClasseVehicule,
	date-du-passage Date-YMMDD-Tis,
	heure-du-passage HeureDuPassage,
	periode-de-tarif PeriodeDeTarif,
	type-de-tarif TypeDeTarif,
	cout-de-la-transaction-ttc CoutDeLaTransactionTTC,
	caractere-d-observation CaractereDeObservation,
	pointeur-d-historique PointeurDeHistorique
}

D-HIS ::= D-VET

D-GES ::= SEQUENCE{
	date-limite-execption-grise Date-YMMDD-Tis,
	reserved OCTET STRING(SIZE(8))
}
D-PASS ::= OCTET STRING(SIZE(40))

SerialNumber ::= OCTET STRING(SIZE(4))
Date-YYWW-Tis ::= SEQUENCE{
	year INTEGER(0..99),
	week INTEGER(1..53)
}

D-EVE ::= SEQUENCE{
	numero-de-serie-du-telebadge SerialNumber,
	date-fabrication Date-YYWW-Tis
}

AnomalyBits ::= SEQUENCE{
	logical-error BOOLEAN,
	reserved1 BOOLEAN,
	reserved2 BOOLEAN,
	missing-data BOOLEAN,
	black-list BOOLEAN,
	reserved5 BOOLEAN,
	reserved6 BOOLEAN,
	reserved7 BOOLEAN
}
D-OBS ::= SEQUENCE {
	erreur-logique AnomalyBits
}

TisContainer ::= CHOICE {
	integer							[0]	 INTEGER,
	reserved1						[1]	 NULL,
	octetstring						[2]	 OCTET STRING (SIZE (0..127, ...)),
	universalString					[3]	 UniversalString,
	beaconId						[4]	 NULL,
	t-apdu							[5]	 NULL,
	dsrcApplicationEntityId			[6]	 NULL,
	dsrc-Ase-Id						[7]	 NULL,
	attrIdList						[8]	 NULL,
	attrList						[9]	 NULL,

	reserved10						[10]	NULL,
	reserved11						[11]	NULL,
	reserved12						[12]	NULL,
	reserved13						[13]	NULL,
	reserved14						[14]	NULL,
	time							[15]	NULL,
	vector							[16]	SEQUENCE (SIZE(0..255)) OF INTEGER(0..127,...),
	reserved17						[17]	NULL,
	reserved18						[18]	NULL,   
	reserved19						[19]	NULL,

	reserved20						[20]	NULL,
	reserved21						[21]	NULL,
	reserved22						[22]	NULL,
	reserved23						[23]	NULL,
	reserved24						[24]	NULL,
	reserved25						[25]	NULL,
	reserved26						[26]	NULL,
	reserved27						[27]	NULL,
	reserved28						[28]	NULL,
	reserved29						[29]	NULL,

	reserved30						[30]	NULL,
	reserved31						[31]	NULL,
	reserved32						[32]	NULL,
	reserved33						[33]	NULL,
	reserved34						[34]	NULL,
	reserved35						[35]	NULL,
	reserved36						[36]	NULL,
	reserved37						[37]	NULL,
	reserved38						[38]	NULL,
	reserved39						[39]	NULL,

	reserved40						[40]	NULL,
	reserved41						[41]	NULL,
	reserved42						[42]	NULL,
	reserved43						[43]	NULL,
	reserved44						[44]	NULL,
	reserved45						[45]	NULL,
	reserved46						[46]	NULL,
	reserved47						[47]	NULL,
	reserved48						[48]	NULL,
	reserved49						[49]	NULL,

	reserved50						[50]	NULL,
	reserved51						[51]	NULL,
	reserved52						[52]	NULL,
	reserved53						[53]	NULL,
	reserved54						[54]	NULL,
	reserved55						[55]	NULL,
	reserved56						[56]	NULL,
	reserved57						[57]	NULL,
	reserved58						[58]	NULL,
	reserved59						[59]	NULL,

	reserved60						[60]	NULL,
	reserved61						[61]	NULL,
	reserved62						[62]	NULL,
	reserved63						[63]	NULL,
	reserved64						[64]	NULL,
	reserved65						[65]	NULL,
	reserved66						[66]	NULL,
	reserved67						[67]	NULL,
	reserved68						[68]	NULL,
	reserved69						[69]	NULL,

	reserved70						[70]	NULL,
	reserved71						[71]	NULL,
	reserved72						[72]	NULL,
	reserved73						[73]	NULL,
	reserved74						[74]	NULL,
	reserved75						[75]	NULL,
	reserved76						[76]	NULL,
	reserved77						[77]	NULL,
	reserved78						[78]	NULL,
	reserved79						[79]	NULL,

	reservedForFutureISOCENuse80	[80]	NULL,
	reservedForFutureISOCENuse81	[81]	NULL, 
	reservedForFutureISOCENuse82	[82]	NULL,
	reservedForFutureISOCENuse83	[83]	NULL,
	reservedForFutureISOCENuse84	[84]	NULL,
	reservedForFutureISOCENuse85	[85]	NULL,
	reservedForFutureISOCENuse86	[86]	NULL,

	reservedForFutureISOCENuse87	[87]	NULL,
	reservedForFutureISOCENuse88	[88]	NULL,
	reservedForFutureISOCENuse89	[89]	NULL,
	reservedForFutureISOCENuse90	[90]	NULL,
	reservedForFutureISOCENuse91	[91]	NULL,
	reservedForFutureISOCENuse92	[92]	NULL,

	reservedForFutureISOCENuse93	[93]	NULL,
	reservedForFutureISOCENuse94	[94]	NULL, 
	reservedForFutureISOCENuse95	[95]	NULL,
	reservedForFutureISOCENuse96	[96]	NULL,
	f-idu	[97]	F-IDU,
	d-pro	[98]	D-PRO,
	d-vet	[99]	D-VET,
	d-his0	[100]   D-HIS,
	d-his1	[101]   D-HIS,
	d-his2	[102]   D-HIS,
	d-his3	[103]   D-HIS,
	d-his4	[104]   D-HIS,
	d-his5	[105]   D-HIS,
	d-his6	[106]   D-HIS,
	d-his7	[107]   D-HIS,
	d-his8	[108]   D-HIS,
	d-his9	[109]   D-HIS,
	d-his10	[110]   D-HIS,
	d-his11	[111]   D-HIS,
	d-his12	[112]   D-HIS,
	d-his13	[113]   D-HIS,
	d-his14	[114]   D-HIS,
	d-his15	[115]   D-HIS,
	d-ges	[116]   D-GES,
	reservedForFutureISOCENuse117	[117]   NULL,
	reservedForFutureISOCENuse118	[118]   NULL,
	reservedForFutureISOCENuse119	[119]   NULL,
	reservedForFutureISOCENuse120	[120]   NULL,
	reservedForFutureISOCENuse121	[121]   NULL,
	reservedForFutureISOCENuse122	[122]   NULL,
	reservedForFutureISOCENuse123	[123]   NULL,
	d-pass	[124]   D-PASS,
	d-eve	[125]   D-EVE,
	d-obs	[126]   D-OBS,
	reservedForFutureISOCENuse127	[127]   NULL,
	...
}

END
-- Below imported data from ISO 14816's ASN.1 module
-- AVIAEINumberingAndDataStructures {iso(1) standard(0) 14816 }
-- DEFINITIONS AUTOMATIC TAGS ::= BEGIN
-- EXPORTS ALL;
-- CS5 ::= VisibleString
-- CountryCode ::= BIT STRING(SIZE(10))
-- Value assignment is done in accordance with ISO 3166-1 and by
-- using the ITA.2 alphabet.
-- IssuerIdentifier ::= INTEGER(0 .. 16383)
-- See Annex A of ISO 14816 for registration
-- END
