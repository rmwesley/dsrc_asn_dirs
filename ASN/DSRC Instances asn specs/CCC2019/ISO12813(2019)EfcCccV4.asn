EfcCcc {iso(1) standard(0) 12813 version4(4)}
DEFINITIONS AUTOMATIC TAGS
::= BEGIN
IMPORTS 
-- Imports data attributes and elements from EFC which are used for CCC
EquipmentOBUId, PaymentMeans, LPN, TrailerCharacteristics, VehicleClass, VehicleDimensions, VehicleAxles, 
VehicleWeightLimits, VehicleSpecificCharacteristics, EFC-ContextMark, Provider, VehicleCurrentMaxTrainWeight, 
-- Imports function parameters from the EFC Application Interface Definition
GetStampedRq, GetStampedRs{}, SetMMIRq
FROM EfcDsrcApplication {iso(1) standard(0) 14906 application(0) version7(7)}

-- Imports the L7 DSRCData module data from the EFC Application Interface Definition, i.e. the lower interface within the CCC scope
Action-Request, Action-Response, ActionType, ApplicationList, AttributeIdList, AttributeList, Attributes,
BeaconID, BST, Dsrc-EID, DSRCApplicationEntityID, Event-Report-Request, Event-Report-Response, EventType,
Get-Request, Get-Response, Initialisation-Request, Initialisation-Response, ObeConfiguration, Profile,
ReturnStatus, Time,  VST, ApplicationContextMark
FROM EfcDsrcGeneric {iso(1) standard(0) 14906 generic(1) version8(8)}

-- Imports from Front-End API Context Data
LocalVehicleClassId
FROM EfcAutonomousContextData {iso(1) standard(0) 17575 part3(3) version2(2)};


-- Note the following are the definitions of the CCC functions:

CCC-InitialiseComm-Request ::= BST

CCC-InitialiseComm-Response ::= VST

CCC-DataRetrieval-Request::= Get-Request (WITH COMPONENTS {fill (SIZE(1)), eid, accessCredentials (SIZE(4)), attrIdList})

CCC-DataRetrieval-Response::= Get-Response {CccContainer} (WITH COMPONENTS {..., eid, iid ABSENT})

CCC-AuthDataRetrieval-Request::= Action-Request {CccContainer} (WITH COMPONENTS {mode (TRUE), eid, actionType (0), accessCredentials (SIZE(4)), actionParameter }) 
-- uses actionParameter (GetStampedRq)

CCC-AuthDataRetrieval-Response::= Action-Response {GetStampedRs{CccContainer}} (WITH COMPONENTS {..., iid ABSENT, responseParameter PRESENT}) 

CCC-Notification-Request::= Action-Request {CccContainer} (WITH COMPONENTS {mode, eid (0), actionType (10), actionParameter }) -- uses actionParameter (SetMMIRq) 

CCC-Notification-Response::= Action-Response {CccContainer}(WITH COMPONENTS {..., eid (0), iid ABSENT, responseParameter ABSENT})

CCC-TerminateComm::= Event-Report-Request {CccContainer} (WITH COMPONENTS {mode (FALSE), eid (0), eventType (0)})   

CCC-TestComm-Request::= Action-Request {CccContainer} (WITH COMPONENTS {..., eid (0), actionType (15), accessCredentials ABSENT, iid ABSENT})

CCC-TestComm-Response::= Action-Response {CccContainer} (WITH COMPONENTS {..., fill (SIZE(1)), eid (0), iid ABSENT})

-- NOTE: The following are the definitions of the CCC attributes:

ActiveContexts ::= SEQUENCE OF SEQUENCE{
    tollContext    Provider,
    contextVersion INT1        
    }

CCC-ContextMark ::= EFC-ContextMark

CommunicationStatus ::= SEQUENCE {
    timeOfLastTransmission Time,
    pendingSince           Time    -- pending since when
    }

DistanceRecordingStatus ::= SEQUENCE {
    distRecordingStatus          DistRecordingStatus,
    accumulatedTravelledDistance INT4,      -- in meter modulo max
    deviationFromGnss            INT1Signed 
    }
    
GnssStatus ::= SEQUENCE {
    lastGnssFixLon  Longitude,
    lastGnssFixLat  Latitude,
    lastGnssFixTime Time,
    currentHDOP     CurrentHDOP,
    lastLAC         LastLAC
    }
    
OBEStatusHistory ::= SEQUENCE {
    statusIndicator     StatusIndicator,
    timeWhenChanged     Time,
    timeWhenActived     Time,
    timeWhenObePowered  Time
    }

ExtendedOBEStatusHistory ::= SEQUENCE {
    statusIndicator             StatusIndicator,
    timeWhenChanged             Time,
    previousStatusIndicator     StatusIndicator,
    timeWhenChangedToPrevious   Time,
    timeWhenActived             Time,
    timeWhenObePowered          Time
    }
    
ExtendedOBUStatusHistoryPart1 ::= SEQUENCE {
    statusIndicator             StatusIndicator,
    timeWhenChanged             Time,
    tspStatus                   INT1,
    position                    Position,
    previousStatusIndicator     StatusIndicator,
    timeWhenChangedToPrevious   Time,
    previousTspStatus           INT1,
    previousPosition            Position,
    timeWhenActived             Time,
    timeWhenObePowered          Time
    }

ExtendedOBUStatusHistoryPart2 ::= SEQUENCE {
    previousStatusIndicator2    StatusIndicator,
    previousTspStatus2          INT1,
    timeWhenChangedToPrevious2  Time,
    previousPosition2           Position,
    previousStatusIndicator3    StatusIndicator,
    previousTspStatus3          INT1,
    timeWhenChangedToPrevious3  Time,
    previousPosition3           Position    
    }


VehicleAxlesHistory ::= SEQUENCE {
    timeWhenChanged				Time,
    previousVehicleAxles    	VehicleAxles
    }

ExtendedVehicleAxlesHistory ::= SEQUENCE {
    timeWhenChanged             Time,
    previousVehicleAxles        VehicleAxles,
    timeWhenChangedToPrevious   Time
    }


VehicleWeightHistory ::= SEQUENCE {
    timeWhenChangedToCurrentValue   Time,
    previousVehicleWeight           VehicleCurrentMaxTrainWeight,
    previousLocalVehicleClassID     LocalVehicleClassId,
    timeWhenChangedToPrevious       Time
    }
    
UserConfirmation ::= SEQUENCE {
   timeOfConfirmation        Time,
   positionOfConfirmation    Position,
   tspStatus                 INT1
}


StatusIndicator ::= INTEGER {
    noGo                    (0),
    go                      (1),
    noGoContractual         (2),
    noGoUserSwitchedOff     (3),
	noGoPaymentMeans        (4),
	goSuspicion 	        (5)
    -- (6..255) are reserved for future use
    } (0..255)

VehicleLicensePlateNumber ::= LPN (WITH COMPONENTS {..., licencePlateNumber (SIZE(14))})

AttributeUpdateInterval ::=  INT1

Position ::= SEQUENCE {
    gnssLon  Longitude,
    gnssLat  Latitude
}

-- NOTE: The following are the definitions of data elements in the CCC attributes:

CurrentHDOP ::= SEQUENCE {
    hDOP                        INT1,       -- HDOP value, keep max
    numberOfUsedSatellites      INT1        -- Number of satellites from which a GNSS signal 
                                            -- is received
    }

INT1 ::=        INTEGER(0..255)
INT1Signed::=   INTEGER(-128..127)
INT2 ::=        INTEGER(0..65535)
INT2Signed ::=  INTEGER (-32768..32767)
INT4 ::=        INTEGER(0..4294967295)
INT4Signed ::=  INTEGER(-2147483648..2147483647)

LastLAC ::= SEQUENCE {
    timeOfLAC   Time, 
    lACOperator Provider,
    rSEId       INT2
    }

Latitude ::= INT4Signed

Longitude ::= INT4Signed

DistRecordingStatus ::= INTEGER {
    notPresent              (1),
    presentAndActive        (2),
    presentAndInactive      (3),
    reservedForFutureUse    (4)
} (0..255)


-- Adoption of T-APDUs for CCC
CCC-T-APDUs ::= CHOICE {
    action-request          [0] Action-Request{CccContainer},
    action-response         [1] Action-Response{CccContainer},
    event-report-request    [2] Event-Report-Request{CccContainer},  
    event-report-response   [3] Event-Report-Response, 
    reserved4               [4] NULL,       -- set-request
    reserved5               [5] NULL,       -- set-response
    get-request             [6] Get-Request,
    get-response            [7] Get-Response{CccContainer},
    initialisation-request  [8] Initialisation-Request,
    initialisation-response [9] Initialisation-Response
}

--Note: the following is the extension of the Layer 7 module


CccContainer ::= CHOICE {
    integer                         [0]     INTEGER,
    reserved1                       [1]     NULL,
    octetstring                     [2]     OCTET STRING (SIZE (0..127, ...)),
    universalString                 [3]     UniversalString,
    beaconId                        [4]     BeaconID,
    t-apdu                          [5]     CCC-T-APDUs,
    dsrcApplicationEntityId         [6]     DSRCApplicationEntityID,
    dsrc-Ase-Id                     [7]     Dsrc-EID,
    attrIdList                      [8]     AttributeIdList,
    attrList                        [9]     AttributeList{CccContainer},

    reserved10                      [10]    NULL,
    reserved11                      [11]    NULL,
    reserved12                      [12]    NULL,
    reserved13                      [13]    NULL,
    reserved14                      [14]    NULL,
    time                            [15]    Time,
    reserved16                      [16]    NULL,
    gstrq                           [17]    GetStampedRq,
    gstrs                           [18]    GetStampedRs{CccContainer},
    reserved19                      [19]    NULL,

    reserved20                      [20]    NULL,
    reserved21                      [21]    NULL,
    reserved22                      [22]    NULL,
    reserved23                      [23]    NULL,
    reserved24                      [24]    NULL,
    reserved25                      [25]    NULL,
    reserved26                      [26]    NULL,
    reserved27                      [27]    NULL,
    reserved28                      [28]    NULL,
    reserved29                      [29]    NULL,

    reserved30                      [30]    NULL,
    reserved31                      [31]    NULL,
    efccontext                      [32]    EFC-ContextMark,
    reserved33                      [33]    NULL,
    reserved34                      [34]    NULL,
    reserved35                      [35]    NULL,
    reserved36                      [36]    NULL,
    reserved37                      [37]    NULL,
    reserved38                      [38]    NULL,
    reserved39                      [39]    NULL,

    reserved40                      [40]    NULL,
    reserved41                      [41]    NULL,
    reserved42                      [42]    NULL,
    reserved43                      [43]    NULL,
    reserved44                      [44]    NULL,
    reserved45                      [45]    NULL,
    reserved46                      [46]    NULL,
    vehlpn                          [47]    LPN,                -- vehicle licence plate number
    reserved48                      [48]    NULL,
    vehclass                        [49]    VehicleClass,

    vehdims                         [50]    VehicleDimensions,
    vehaxles                        [51]    VehicleAxles,
    vehwtlims                       [52]    VehicleWeightLimits,
    reserved53                      [53]    NULL,
    vehspchars                      [54]    VehicleSpecificCharacteristics,
    reserved55                      [55]    NULL,
    equOBUId                        [56]    EquipmentOBUId,
    reserved57                      [57]    NULL,
    reserved58                      [58]    NULL,
    reserved59                      [59]    NULL,

    reserved60                      [60]    NULL,
    reserved61                      [61]    NULL,
    reserved62                      [62]    NULL,
    reserved63                      [63]    NULL,
    paymeans                        [64]    PaymentMeans,
    reserved65                      [65]    NULL,
    reserved66                      [66]    NULL,
    reserved67                      [67]    NULL,
    reserved68                      [68]    NULL,
    setmmirq                        [69]    SetMMIRq,

    reserved70                      [70]    NULL,
    reserved71                      [71]    NULL,
    reserved72                      [72]    NULL,
    reserved73                      [73]    NULL,
    reserved74                      [74]    NULL,
    reserved75                      [75]    NULL,
    reserved76                      [76]    NULL,
    reserved77                      [77]    NULL,
    reserved78                      [78]    NULL,
    tch                             [79]    TrailerCharacteristics,
    
    reserved80                      [80]    NULL,
    vehicleAxlesHistory             [81]    VehicleAxlesHistory,
    communicationStatus             [82]    CommunicationStatus,
    gnssStatus                      [83]    GnssStatus,
    distanceRecordingStatus         [84]    DistanceRecordingStatus,
    activeContexts                  [85]    ActiveContexts,
    oBEStatusHistory                [86]    OBEStatusHistory,
    
    reservedForFutureISOCENuse87    [87]    NULL,
    reservedForFutureISOCENuse88    [88]    NULL,
    reservedForFutureISOCENuse89    [89]    NULL,
    reservedForFutureISOCENuse90    [90]    NULL,
    reservedForFutureISOCENuse91    [91]    NULL,
    reservedForFutureISOCENuse92    [92]    NULL,
    
    vehicleWeightHistory            [93]    VehicleWeightHistory,
    extendedOBEStatusHistory        [94]    ExtendedOBEStatusHistory,
    extendedVehicleAxlesHistory     [95]    ExtendedVehicleAxlesHistory,
    localVehicleClassId             [96]    LocalVehicleClassId,
    vehicleCurrentMaxTrainWeight    [97]    VehicleCurrentMaxTrainWeight,
    attributeUpdateInterval         [98]    AttributeUpdateInterval,

    extendedOBUStatusHistoryPart1   [99]    ExtendedOBUStatusHistoryPart1,
    extendedOBUStatusHistoryPart2   [100]   ExtendedOBUStatusHistoryPart2,
    userConfirmation				[101]   UserConfirmation,
    reservedForFutureISOCENuse102   [102]   NULL,

    reservedForFutureISOCENuse103   [103]   NULL,
    reservedForFutureISOCENuse104   [104]   NULL,
    reservedForFutureISOCENuse105   [105]   NULL,
    reservedForFutureISOCENuse106   [106]   NULL,
    reservedForFutureISOCENuse107   [107]   NULL,
    reservedForFutureISOCENuse108   [108]   NULL,
    reservedForFutureISOCENuse109   [109]   NULL,
    reservedForFutureISOCENuse110   [110]   NULL,
    reservedForFutureISOCENuse111   [111]   NULL,
    reservedForFutureISOCENuse112   [112]   NULL,
    ...
    }

END
