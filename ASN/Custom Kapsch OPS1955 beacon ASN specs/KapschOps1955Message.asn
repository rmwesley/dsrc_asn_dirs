KapschOps1955Message {kapsch(1) ops1955(0) messages(0) version1(0) minorVersion1(1)}
DEFINITIONS AUTOMATIC TAGS 
::= BEGIN
EXPORTS ALL;
IMPORTS
-- ********* ISO 17573-3:2022 *********
	ActualNumberOfPassengers, AxleWeightLimits, Co2EmissionValue, ContractSerialNumber, ContractAuthenticator, ContractValidity, 
	DieselEmissionValues, DriverCharacteristics, EfcContextMark, EngineDetails, EquipmentIccId, EquipmentObuId, EquipmentStatus, ExhaustEmissionValues, 
	Lpn, PassengerCapacity, PaymentMeans, PaymentMeansBalance, PaymentSecurityData, ReceiptAuthenticator, ReceiptContract, ReceiptDistance, 
	ReceiptFinancialPart, ReceiptIccId, ReceiptObuId, ReceiptServicePart, ReceiptServiceSerialNumber, ReceiptText, SessionClass, SoundLevel, 
	TrailerCharacteristics, ValidityOfContract, VehicleAuthenticator, VehicleAxles, VehicleClass, VehicleDimensions, VehicleIdentificationNumber, 
	VehicleSpecificCharacteristics, VehicleTotalDistance, VehicleWeightLaden, VehicleWeightLimits
	FROM KapschOps1955DataDictionary {kapsch(1) ops1955(0) datadict version1(0) minorVersion1(1)} WITH SUCCESSORS

-- ********* ISO/FDIS 14906:2022 generic *********
	Action-Request{}, Action-Response{}, ActionType, ApplicationList, AttributeIdList, AttributeList{}, Attributes{},
	BeaconID, BST, Dsrc-EID, DSRCApplicationEntityID, Event-Report-Request{}, Event-Report-Response, EventType,
    Set-Request, Set-Response,
	Get-Request, Get-Response{}, Initialisation-Request, Initialisation-Response, ObeConfiguration, Profile,
	ReturnStatus, VST, ApplicationContextMark,
    EfcContainer, Time
	FROM EfcDsrcGeneric {iso(1) standard(0) 14906 generic(1) version10(10) minorVersion1(1)} WITH SUCCESSORS;

-- ********* ISO/FDIS 14906:2022 application *********
	AddRq, ChannelRq, ChannelRs, CopyRq, CreditRq, CreditRs, DebitRq, DebitRs, GetInstanceRq, GetInstanceRs{}, GetStampedRq, GetStampedRs{}, 
	SetInstanceRq{}, SetMMIRq, SetStampedRq{}, SubRq,
	PaymentMeansUnit, --type re-definition of PayUnitkept for descriptive reasons in the body of the standard
	ReceiptData1, ReceiptData2, --type re-definitions of ReceiptData kept for descriptive reasons in the body of the standard
	ContractVehicle, TrailerLicencePlateNumber --type re-definitions of Lpn kept for descriptive reasons in the body of the standard
	FROM EfcDsrcApplication {iso(1) standard(0) 14906 application(0) version9(9) minorVersion1(1)} WITH SUCCESSORS;


OPS1955Container ::= EfcContainer

Lic-Return-Status ::= INTEGER{
    ok (0),
    wrong-version-number (1),
    unknown-class (2),
    unknown-instance (3),
    unknown-message-number (4),
    invalid-length-of-data-field (5),
    invalid-data (6),
    parameters-affecting-the-accessed-command-not-set-properly (7),
    command-failed (8)
}(0..8)

DSRC-Return-Status ::= SEQUENCE{
    link-id OCTET STRING (SIZE(4)),
    message-status Lic-Return-Status
}

Action-Confirmation ::= SEQUENCE {
    link-id INTEGER(0..255),
    response-parameter-bit-map BOOLEAN,
    return-status-bit-map BOOLEAN,
    element-id INTEGER(0..255),
    response-parameter OPS1955Container,
    return-status DSRC-Return-Status,
    instance INTEGER(0..255)
}

Set-Confirmation ::= SEQUENCE {
    link-id INTEGER(0..255),
    return-status-bit-map BOOLEAN,
    element-id INTEGER(0..255),
    return-status DSRC-Return-Status,
    instance INTEGER(0..255)
}

Get-Confirmation ::= SEQUENCE {
    link-id INTEGER(0..255),
    attribute-list-bit-map BOOLEAN,
    return-status-bit-map BOOLEAN,
    element-id INTEGER(0..255),
    attribute-list AttributeList{OPS1955Container},
    return-status DSRC-Return-Status,
    instance INTEGER(0..255)
}

OBE-Configuration ::= SEQUENCE {
    equipment-class INTEGER(0..255),
    manufacturer-id INTEGER(0..255),
    obe-status INTEGER(0..255)
}

Notify-Application-Beacon ::= SEQUENCE {
    trx-no INTEGER(0..255),
    link-id INTEGER(0..255),
    application-list ApplicationList,
    obe-configuration OBE-Configuration
}

Ready-Application ::= SEQUENCE {
    flow-control-priority INTEGER(0..255),
    application-id INTEGER(0..255),
    link-id INTEGER(0..255)
}

Notify-Application-Lost-Message ::= SEQUENCE {
    link-id INTEGER(0..255),
    value INTEGER(0..255)
}

Forced-Release ::= SEQUENCE {
    application-id INTEGER(0..255),
    link-id INTEGER(0..255)
}

Tis-Ready-Application ::= SEQUENCE {
    flow-control-priority INTEGER(0..255),
    application-id INTEGER(0..255),
    link-id INTEGER(0..255),
    eid INTEGER(0..255)
}

TRX-Status ::= BIT STRING {
    warning (15),
    major-error (14),
    erroneous-value-b (13),
    erroneous-value-a (12),
    microwave-transmitter-power-failure (11),
    voltage-error (10),
    communciation-error (9),
    beacon-not-configured (8),
    control-data-processor-not-ready-ot-busy (7),
    bit-busy-or-not-ready (6),
    illegal-command (5)
    value-out-of-range (4),
    password-error (3),
    illegal-command-sequence (2),
    trx-not-present (1),
    trx-occupied (0)
}(SIZE(16))

TRX-Mode ::= BIT STRING{
    my-power-off (0),
    my-power-on (1),
    frequency-2-not-1point5 (2),
    localization-mode (3),
    bst-time-slots-3-not-2 (4)
    spare5 (5),
    spare6 (6),
    spare7 (7)
}(SIZE(8))

TRX-Status-Req-Message ::= SEQUENCE {
    instance INTEGER(0..255)
}

TRX-Status-Message ::= SEQUENCE {
    instance INTEGER(0..255),
    status TRX-Status,
    trx-mode TRX-Mode
}

TRX-ID ::= SEQUENCE {
    instance INTEGER(0..255),
    status TRX-Status,
    trx-id SEQUENCE (SIZE(8)) OF INTEGER(0..255),
    hwid TRX-Status,
    swid SEQUENCE (SIZE(3)) OF INTEGER(0..255)
}

TRX-Internal-Humidity ::= SEQUENCE {
    instance INTEGER(0..255),
    status TRX-Status,
    humid INTEGER(0..255)
}

TRX-Internal-Temperature ::= SEQUENCE {
    instance INTEGER(0..255),
    status TRX-Status,
    temp INTEGER(0..255)
}

My-Power-Mode ::= INTEGER {
    off (0),
    on (2)
}(0..255)

TRX-My-Power-Mode ::= SEQUENCE {
    instance INTEGER(0..255),
    mode My-Power-Mode
}

TRX-Carrier-Frequency ::= SEQUENCE {
    instance INTEGER(0..255),
    status TRX-Status, -- Present only for ID 1415
    cfq INTEGER(0..255)
}

TRX-Uplink-Parameters ::= SEQUENCE {
    instance INTEGER(0..255),
    upl INTEGER(0..255)
}

TRX-Output-Power ::= SEQUENCE {
    instance INTEGER(0..255),
    status TRX-Status, -- Present only for ID 1416
    spw INTEGER(0..255)
}

TRX-Echo ::= SEQUENCE {
    instance INTEGER(0..255),
    data OCTET STRING (SIZE(122)),
    length INTEGER(0..255) -- LiC ETC specific
}

UI-Control-OPS1925 ::= SEQUENCE {
    mode INTEGER(0..255),
    green-led INTEGER(0..255),
    orange-led INTEGER(0..255),
    red-led INTEGER(0..255)
}

UI-Control-OPS1955 ::= SEQUENCE {
    red INTEGER(0..255),
    green INTEGER(0..255),
    blue INTEGER(0..255)
}

TRX-Set-UI-Control ::= SEQUENCE {
    instance INTEGER(0..255),
    status TRX-Status, -- Uplink only
    ui-type UI-Type,
    ops1925 UI-Control-OPS1925, -- Dnlink only, only for OPS1925
    ops1955 UI-Control-OPS1955 -- Dnlink only, only for OPS1955
}

Read-UI-Control ::= SEQUENCE {
    instance INTEGER(0..255),
    status TRX-Status, -- Uplink only
    uitype UI-Type,
    mode INTEGER(0..255), -- Dnlink only, only for OPS1925
    ops1925 UI-Control-OPS1925, -- Uplink only, only for OPS1925
    ops1955 UI-Control-OPS1955 -- Uplink only, only for OPS1955
}

UI-Type ::= INTEGER{
    ops1925-switch (0),
    ops1955-infrared-sensor (1)
}(0..255)

UI-Sensors-Status ::= BIT STRING{
    door-open (0),
    no-object-detected (1)
}(SIZE(8))

TRX-UI-Status ::= SEQUENCE {
    instance INTEGER(0..255),
    status TRX-Status, -- Uplink only
    ui-type UI-Type, -- Uplink only
    ui-sensors-status UI-Sensors-Status -- Uplink only
}

TRX-General-Purpose ::= SEQUENCE {
    instance INTEGER(0..255),
    password OCTET STRING (SIZE(8)), -- Dnlink only
    genid INTEGER(0..255), -- Dnlink only
    genda-genre OCTET STRING (SIZE(255)),
    status TRX-Status, -- Uplink only
    length INTEGER -- Length of GENDA_GENRE (LiC ETC specific)
}

TRX-Extended-Output-Power ::= SEQUENCE {
    instance INTEGER(0..255),
    password OCTET STRING (SIZE(8)),
    spw INTEGER(0..255)
}

TRX-Set-RF-Param ::= SEQUENCE {
    instance INTEGER(0..255),
    password OCTET STRING (SIZE(8)),
    id INTEGER(0..255),
    data INTEGER(0..255)
}

TRX-Read-RF-Param ::= SEQUENCE {
    instance INTEGER(0..255),
    password OCTET STRING (SIZE(8)), -- Dnlink only
    id1 INTEGER, -- Dnlink only
    id2 INTEGER, -- Dnlink only
    data OCTET STRING (SIZE(255)), -- Uplink only
    length INTEGER
}

Lic-Nalm-Behaviour ::= SEQUENCE {
    message-status Lic-Return-Status,
    behaviour INTEGER(0..255)
}

Lic-PDU-No-Behaviour ::= SEQUENCE {
    message-status Lic-Return-Status,
    behaviour INTEGER(0..255)
}

Lic-L7-Ack-Mode ::= SEQUENCE {
    message-status Lic-Return-Status,
    mode INTEGER(0..255)
}

Lic-Private-Uplink-Window-Time ::= SEQUENCE {
    message-status Lic-Return-Status,
    uplink-window-time INTEGER(0..255)
}

Lic-Slow-Data-Behaviour ::= SEQUENCE {
    message-status Lic-Return-Status,
    slow-data-behaviour INTEGER(0..255)
}

Lic-Release-Retransmissions ::= SEQUENCE {
    message-status Lic-Return-Status,
    retransmissions INTEGER(0..255)
}

Lic-LID-Cleanup-Mode ::= SEQUENCE {
    message-status Lic-Return-Status,
    lid-cleanup-mode INTEGER(0..255)
}

Mode ::= INTEGER{
    off (0),
    on (1),
    paused (2),
    single-shot (3),
    single-shot-with-obu-detection (4)
}(0..4)

Set-DSRC-Link-Mode ::= SEQUENCE {
    mode Mode
}

Read-DSRC-Link-Mode ::= SEQUENCE {
    message-status Lic-Return-Status, -- Present only for ID 2451
    mode INTEGER(0..255)
}

DSRC-Configuration ::= SEQUENCE {
    message-status Lic-Return-Status, -- Present only for ID 2456
    trx-position INTEGER(0..255),
    bst-mode INTEGER(0..255),
    low-priority-bst-cycle-time INTEGER(0..255),
    high-priority-bst-cycle-time INTEGER(0..255),
    max-cycle-time-llc-retransmissions-level-1 INTEGER(0..255),
    max-cycle-time-llc-retransmissions-level-2 INTEGER(0..255),
    max-cycle-time-llc-retransmissions-level-3 INTEGER(0..255),
    max-cycle-time-llc-retransmissions-level-4 INTEGER(0..255),
    max-nr-llc-retransmissions-level-1 INTEGER(0..255),
    max-nr-llc-retransmissions-level-2 INTEGER(0..255),
    max-nr-llc-retransmissions-level-3 INTEGER(0..255),
    max-nr-llc-retransmissions-level-4 INTEGER(0..255),
    max-nr-mac-retransmissions INTEGER(0..255)
}

Set-BST-Configuration ::= SEQUENCE {
    rsu BeaconID,
    profile Profile,
    mandApplications ApplicationList
}

KapschProfile::= INTEGER {
	profile0 (0), -- DSRC Profile 0 as defined in EN 13372
	profile1 (1) -- DSRC Profile 1 as defined in EN 13372
	-- (2..118) are reserved for ISO/CEN use,
	-- (119..127) are reserved for private use
}(0..255)

Read-BST-Configuration ::= SEQUENCE {
    message-status Lic-Return-Status, -- Present only for ID 2458
    rsu BeaconID,
    profile KapschProfile,
    mandApplications ApplicationList
}

KapschTime ::= SEQUENCE {
    message-status Lic-Return-Status, -- Present only for ID 2460
    unix-time Time,
    milliseconds INTEGER(0..65535)
}

General-Log-Level ::= SEQUENCE {
    message-status Lic-Return-Status, -- Present only for ID 2464
    log-level INTEGER(0..255)
}

Log-Category-Mode ::= SEQUENCE {
    message-status Lic-Return-Status, -- Present only for ID 2466 (to host)
    log-category INTEGER(0..255),
    mode INTEGER -- Not used in 2466 (from host)
}

Transaction-Status ::= SEQUENCE {
    message-status Lic-Return-Status,
    transaction-status INTEGER(0..255)
}

Echo ::= SEQUENCE {
    length INTEGER(0..255), -- LiC ETC specific
    data OCTET STRING (SIZE(500))
}

Communication-Log-Result ::= SEQUENCE {
    link-identifier INTEGER(0..255),
    trx-no INTEGER(0..255),
    data-age INTEGER(0..255),
    angle-a INTEGER(0..255),
    angle-b INTEGER(0..255),
    angular-quality INTEGER(0..255),
    signal-level-uplink INTEGER(0..255),
    frame-length INTEGER(0..255)
}

LiC-Status ::= INTEGER(0..65535)

LiC-Status-Message ::= SEQUENCE {
    message-status Lic-Return-Status,
    lic-status LiC-Status,
    trx-1-status TRX-Status,
    trx-2-status TRX-Status,
    trx-3-status TRX-Status,
    trx-4-status TRX-Status,
    trx-5-status TRX-Status,
    trx-6-status TRX-Status,
    trx-7-status TRX-Status,
    trx-8-status TRX-Status
}

LiC-Statistics ::= SEQUENCE {
    message-status Lic-Return-Status, -- To host only
    module-id INTEGER(0..255),
    number-of-parameters INTEGER(0..255), -- To host only
    parameter SEQUENCE (SIZE(40)) OF INTEGER -- To host only
}

Status-Mode ::= SEQUENCE {
    message-status Lic-Return-Status, -- Present only for ID 2754
    mode INTEGER(0..255),
    interval INTEGER(0..255)
}

LiC-Version ::= SEQUENCE {
    lic-serial-number OCTET STRING (SIZE(8)),
    lic-sw-version OCTET STRING (SIZE(4))
}

KapschRequestMessages ::= CHOICE{
	action-request			    [0]	Action-Request{OPS1955Container},
	action-response			    [1]	Action-Response{OPS1955Container},
	event-report-request	    [2]	Event-Report-Request{OPS1955Container},
	event-report-response	    [3]	Event-Report-Response,
	set-request				    [4]	Set-Request{OPS1955Container},
	set-response			    [5]	Set-Response,
	get-request				    [6]	Get-Request,
	get-response			    [7]	Get-Response{OPS1955Container},
	initialisation-request  	[8]	Initialisation-Request,
	initialisation-response	    [9]	Initialisation-Response,
	notify-application-beacon   [12] Notify-Application-Beacon,
	ready-application           [13] Ready-Application,
	notify-application-lost-message [14] Notify-Application-Lost-Message,
	send-bst                  	[17] Lic-Return-Status,
	forced-release              [18] Forced-Release,
	tis-ready-application1      [103] Tis-Ready-Application,
	tis-ready-application2      [105] Tis-Ready-Application,
	read-trx-status             [1401] TRX-Status-Req-Message,
	trx-id                      [1402] TRX-ID,
	trx-internal-humidity       [1403] TRX-Internal-Humidity,
	trx-internal-temperature    [1404] TRX-Internal-Temperature,
	set-trx-my-power-mode       [1405] TRX-My-Power-Mode,
	trx-carrier-frequency1      [1406] TRX-Carrier-Frequency,
	trx-carrier-frequency2      [1415] TRX-Carrier-Frequency,
	trx-uplink-parameters       [1407] TRX-Uplink-Parameters,
	trx-output-power1           [1408] TRX-Output-Power,
	trx-output-power2           [1416] TRX-Output-Power,
	trx-echo                    [1414] TRX-Echo,
	trx-set-ui-control          [1420] TRX-Set-UI-Control,
	read-ui-control             [1421] Read-UI-Control,
	read-ui-status              [1422] NULL,
	trx-general-purpose         [1500] TRX-General-Purpose,
	trx-extended-output-power   [1506] TRX-Extended-Output-Power,
	trx-read-rf-param1          [1516] TRX-Read-RF-Param,
	trx-read-rf-param2          [1517] TRX-Read-RF-Param,
	lic-nalm-behaviour1         [2408] Lic-Nalm-Behaviour,
	lic-nalm-behaviour2         [2409] Lic-Nalm-Behaviour,
	lic-pdu-no-behaviour1       [2410] Lic-PDU-No-Behaviour,
	lic-pdu-no-behaviour2       [2411] Lic-PDU-No-Behaviour,
	lic-l7-ack-mode1            [2412] Lic-L7-Ack-Mode,
	lic-l7-ack-mode2            [2413] Lic-L7-Ack-Mode,
	lic-private-uplink-window-time1 [2414] Lic-Private-Uplink-Window-Time,
	lic-private-uplink-window-time2 [2415] Lic-Private-Uplink-Window-Time,
	lic-slow-data-behaviour1    [2416] Lic-Slow-Data-Behaviour,
	lic-slow-data-behaviour2    [2417] Lic-Slow-Data-Behaviour,
	lic-release-retransmissions1 [2418] Lic-Release-Retransmissions,
	lic-release-retransmissions2 [2419] Lic-Release-Retransmissions,
	lic-lid-cleanup-mode1       [2420] Lic-LID-Cleanup-Mode,
	lic-lid-cleanup-mode2       [2421] Lic-LID-Cleanup-Mode,
	set-dsrc-link-mode          [2450] Set-DSRC-Link-Mode,
	read-dsrc-link-mode         [2451] NULL,
	dsrc-configuration1         [2455] DSRC-Configuration,
	dsrc-configuration2         [2456] DSRC-Configuration,
	set-bst-configuration       [2457] Set-BST-Configuration,
	read-bst-configuration      [2458] NULL,
	time1                       [2459] KapschTime,
	time2                       [2460] KapschTime,
	general-log-level1          [2463] General-Log-Level,
	general-log-level2          [2464] General-Log-Level,
	log-category-mode1          [2465] Log-Category-Mode,
	log-category-mode2          [2466] Log-Category-Mode,
	transaction-status1         [2482] Transaction-Status,
	transaction-status2         [2483] Transaction-Status,
	echo                        [2605] Echo,
	communication-log-result    [2650] Communication-Log-Result,
	lic-status1                 [2651] LiC-Status-Message,
	lic-status2                 [2752] LiC-Status-Message,
	lic-statistics              [2751] LiC-Statistics,
	status-mode1                [2753] Status-Mode,
	status-mode2                [2754] Status-Mode
} (WITH COMPONENTS { ... })

KapschResponseMessages ::= CHOICE{
	action-request			    [0]	DSRC-Return-Status,
	action-response			    [1]	Action-Response{OPS1955Container},
	event-report-request	    [2]	Event-Report-Request{OPS1955Container},
	event-report-response	    [3]	Event-Report-Response,
	set-request				    [4]	Set-Request{OPS1955Container},
	set-response			    [5]	Set-Response,
	get-request				    [6]	Get-Request,
	get-response			    [7]	Get-Response{OPS1955Container},
	initialisation-request  	[8]	Initialisation-Request,
	initialisation-response	    [9]	Initialisation-Response,
	notify-application-beacon   [12] Notify-Application-Beacon,
	ready-application           [13] Ready-Application,
	notify-application-lost-message [14] Notify-Application-Lost-Message,
	send-bst                  	[17] Lic-Return-Status,
	forced-release              [18] Forced-Release,
	tis-ready-application1      [103] Tis-Ready-Application,
	tis-ready-application2      [105] Tis-Ready-Application,
	read-trx-status             [1401] TRX-Status-Message,
	trx-id                      [1402] TRX-ID,
	trx-internal-humidity       [1403] TRX-Internal-Humidity,
	trx-internal-temperature    [1404] TRX-Internal-Temperature,
	set-trx-my-power-mode       [1405] TRX-Status-Message,
	trx-carrier-frequency1      [1406] TRX-Carrier-Frequency,
	trx-carrier-frequency2      [1415] TRX-Carrier-Frequency,
	trx-uplink-parameters       [1407] TRX-Uplink-Parameters,
	trx-output-power1           [1408] TRX-Output-Power,
	trx-output-power2           [1416] TRX-Output-Power,
	trx-echo                    [1414] TRX-Echo,
	set-trx-ui-control          [1420] TRX-Set-UI-Control,
	read-ui-control             [1421] Read-UI-Control,
	read-ui-status              [1422] TRX-UI-Status,
	report-ui-status            [1423] TRX-UI-Status,
	trx-general-purpose         [1500] TRX-General-Purpose,
	trx-extended-output-power   [1506] TRX-Extended-Output-Power,
	trx-read-rf-param1          [1516] TRX-Read-RF-Param,
	trx-read-rf-param2          [1517] TRX-Read-RF-Param,
	lic-nalm-behaviour1         [2408] Lic-Nalm-Behaviour,
	lic-nalm-behaviour2         [2409] Lic-Nalm-Behaviour,
	lic-pdu-no-behaviour1       [2410] Lic-PDU-No-Behaviour,
	lic-pdu-no-behaviour2       [2411] Lic-PDU-No-Behaviour,
	lic-l7-ack-mode1            [2412] Lic-L7-Ack-Mode,
	lic-l7-ack-mode2            [2413] Lic-L7-Ack-Mode,
	lic-private-uplink-window-time1 [2414] Lic-Private-Uplink-Window-Time,
	lic-private-uplink-window-time2 [2415] Lic-Private-Uplink-Window-Time,
	lic-slow-data-behaviour1    [2416] Lic-Slow-Data-Behaviour,
	lic-slow-data-behaviour2    [2417] Lic-Slow-Data-Behaviour,
	lic-release-retransmissions1 [2418] Lic-Release-Retransmissions,
	lic-release-retransmissions2 [2419] Lic-Release-Retransmissions,
	lic-lid-cleanup-mode1       [2420] Lic-LID-Cleanup-Mode,
	lic-lid-cleanup-mode2       [2421] Lic-LID-Cleanup-Mode,
	set-dsrc-link-mode          [2450] DSRC-Return-Status,
	read-dsrc-link-mode         [2451] Read-DSRC-Link-Mode,
	dsrc-configuration1         [2455] DSRC-Configuration,
	dsrc-configuration2         [2456] DSRC-Configuration,
	set-bst-configuration       [2457] Lic-Return-Status,
	read-bst-configuration      [2458] Read-BST-Configuration,
	time1                       [2459] KapschTime,
	time2                       [2460] KapschTime,
	general-log-level1          [2463] General-Log-Level,
	general-log-level2          [2464] General-Log-Level,
	log-category-mode1          [2465] Log-Category-Mode,
	log-category-mode2          [2466] Log-Category-Mode,
	transaction-status1         [2482] Transaction-Status,
	transaction-status2         [2483] Transaction-Status,
	echo                        [2605] Echo,
	communication-log-result    [2650] Communication-Log-Result,
	lic-status1                 [2651] LiC-Status-Message,
	lic-status2                 [2752] LiC-Status-Message,
	lic-statistics              [2751] LiC-Statistics,
	status-mode1                [2753] Status-Mode,
	status-mode2                [2754] Status-Mode
} (WITH COMPONENTS { ... })

END
-- Below imported data from ISO 14816's ASN.1 module
-- AVIAEINumberingAndDataStructures {iso(1) standard(0) 14816 }
-- DEFINITIONS AUTOMATIC TAGS ::= BEGIN
-- EXPORTS ALL;
-- CS5 ::= VisibleString
-- CountryCode ::= BIT STRING(SIZE(10))
-- Value assignment is done in accordance with ISO 3166-1 and by
-- using the ITA.2 alphabet.
-- IssuerIdentifier ::= INTEGER(0 .. 16383)
-- See Annex A of ISO 14816 for registration
-- END
